module ietf-yang-types {

   namespace "urn:ietf:params:xml:ns:yang:ietf-yang-types";
   prefix "inet";

   organization
    "IETF NETMOD (NETCONF Data Modeling Language) Working Group";

   contact
    "Editor:   Juergen Schoenwaelder
               <mailto:j.schoenwaelder@jacobs-university.de>";

   description
    "This .";

   revision 2010-09-24 {
     description
      "Initial revision.";
     reference
      "RFC 6021: Common YANG Data Types";
   }

   typedef ip-address {
        type union {
          type inet:ipv4-address;
        }
        description
         "The ip-address type represents an IP address and is IP
          version neutral.  The format of the textual representations
          implies the IP version.";
      }

      typedef ipv4-address {
        type string {
          pattern
            '(([0-9]|[1-9][0-9]|1[0-9][0-9]|2[0-4][0-9]|25[0-5])\.){3}'
          +  '([0-9]|[1-9][0-9]|1[0-9][0-9]|2[0-4][0-9]|25[0-5])'
          + '(%[\p{N}\p{L}]+)?';
        }
      }
 }
