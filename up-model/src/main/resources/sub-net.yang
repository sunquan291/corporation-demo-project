module sub-net {
    yang-version 1;
    namespace "ip.net.sub";
    prefix sn;

    grouping arp-packet-fields {
        leaf hardware-type {
          type string;
          description "Network protocol type";
        }
    }

    typedef my
    {
        type string;
    }
}
