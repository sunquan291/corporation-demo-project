module ipsdn-device-manager {
    yang-version 1;
    namespace "urn:zte:ngip:ipsdn:device-manager";
    prefix "device";

    import ietf-inet-types {prefix inet; revision-date "2010-09-24"; }
    import opendaylight-inventory {prefix inv;revision-date "2013-08-19";}
    import yang-ext {prefix "ext"; revision-date "2013-07-09";}
    import base-model {prefix "base-model"; revision-date "2017-03-29";}

    organization "zte";

    description
      "YANG version of the device-manager.";

    revision "2015-09-15" {
        description "Initial revision of device-manager model";
    }

    rpc  get-device-netconf {
        input {
            uses node-list;
        }
        output {
            list device-netconf {
                uses device-netconf-detail;
                description "H controller get all device netconf info." ;
            }
        }
    }

    rpc synchronize-device {
        input {
            uses node-list;
        }
    }

    grouping node-list{
        list nodes{
            key "node-id";
            leaf node-id {
                type inv:node-id;
                description "The nodeid of the device.";
            }
        }
    }

    grouping device-netconf-detail {
        leaf node-id {
            type inv:node-id;
            description "The nodeid of the device.";
        }
        leaf device-description {
            type string;
            description "The description of the device.";
        }

        uses netconf-connection;
    }

    grouping netconf-connection {
        description "The netconf-config of a connection between controller and device.";
        leaf netconf-ip {
            type inet:ip-address;
            description "The ip of a connection between controller and device.";
        }
        leaf netconf-port {
            type uint16;
            description "The port of a connection between controller and device.";
        }
        leaf user-name {
            type string;
            description "The name of a connection between controller and device.";
        }
        leaf password {
            type string;
            description "The password of a connection between controller and device.";
        }
    }

    typedef snmp-auth-protocol-type {
        description "The type of SNMP's auth connection between controller and device.";
        type enumeration {
            enum "NO_AUTH" {
                value 20;
                description "There is NO_AUTH of a connection between controller and device.";
            }
            enum "MD5" {
                value 21;
                description "There is MD5 of a connection between controller and device.";
            }
            enum "SHA" {
                value 22;
                description "There is SHA of a connection between controller and device.";
            }
        }
    }

    typedef snmp-encry-protocol-type {
        description "The type of SNMP's encry connection between controller and device.";
        type enumeration {
            enum "NO_AUTH" {
                value 0;
                description "NO_AUTH.";
            }
            enum "CBC_DES" {
                value 1;
                description "CBC_DES.";
            }
            enum "CFB_AES_128" {
                value 2;
                description "CFB_AES_128.";
            }
        }
    }

    typedef snmpv3-security-Level {
        description "The level of SNMPv3's security.";
        type enumeration {
            enum "NoAuthNoEncode" {
                value 0;
                description "NoAuthNoEncode";
            }
            enum "AuthNoEncode" {
                value 1;
                description "AuthNoEncode";
            }
            enum "AuthEncode" {
                value 3;
                description "AuthEncode";
            }
        }
    }

    typedef snmp-version-type {
        description "The version of SNMP.";
        type enumeration {
            enum "v1" {
                value 1;
                description "v1";
            }
            enum "v2c" {
                value 2;
                description "v2";
            }
            enum "v3" {
                value 3;
                description "v3";
            }
        }
    }

    typedef node-type {
        description "The type of node.";
        type enumeration {
            enum "D-CONTROLLER" {
                description "D-CONTROLLER.";
            }
            enum "ACC" {
                description "ACC.";
            }
            enum "AGG" {
                description "AGG.";
            }
            enum "ASBR" {
                description "ASBR.";
            }
            enum "RAN-PE" {
                description "RAN-PE.";
            }
            enum "O-CONTROLLER" {
                description "O-C CONTROLLER.";
            }
            enum "DNA" {
                description "DNA plugin.";
            }
        }
    }

    grouping cli-connection {
        description "The cli-config of a connection between controller and device.";
        leaf name {
            type string;
            description "The name of the connection.";
        }
        leaf ip-address {
            type inet:ip-address;
            description "The ip of the connection.";
        }
        leaf port{
            type uint16;
            description "The port of the connection.";
        }
        leaf user-name {
            type string;
            description "The user-name of the connection.";
        }
        leaf password {
            type string;
            description "The password of the connection.";
        }
        leaf connect-type {
            description "The connect-type of the connection.";
            type enumeration {
                enum "TYPE_TELNET" {
                    value 0;
                    description "TYPE_TELNET.";
                }
                enum "TYPE_SSH" {
                    value 1;
                    description "TYPE_SSH.";
                }
            }
        }
    }

    grouping pcep-connection {
        description "The pcep-config of a connection between controller and device.";
        leaf pcep-peer-ip{
            description "=
                A ip address is specified for whitch D-controller
                is a PCE for added device .
            ";
            type inet:ipv4-address;
        }
        leaf pcep-router-id{
            description "=
                A ip address on added device ,whitch is a PCC.
                this device use the ip address connection to PCE
            ";
            type inet:ipv4-address;
        }

    }

    grouping restconf-connection {
        description "The restconf-config of a connection between controller and device.";
        leaf restconf-ip {
            type inet:ip-address;
            description "The ip of the connection.";
        }
        leaf restconf-port {
            type uint16;
            description "The port of the connection.";
        }
        leaf user-name {
            type string;
            description "The user-name of the connection.";
        }
        leaf password {
            type string;
            description "The password of the connection.";
        }

        leaf-list notification {
            type string;
            description "The messages of the notifications.";
        }
    }

    grouping bgp-connection {
        description "The bgp-config of a connection between controller and device.";
        leaf local-as {
            type string;
            description "The local-as of the connection.";
        }

        leaf local-ip {
            type inet:ip-address;
            description "The local-ip of the connection.";
        }

        leaf remote-ip {
            type inet:ip-address;
            description "The remote-ip of the connection.";
        }

        leaf remote-as {
            type string;
            description "The remote-as of the connection.";
        }
	    leaf bgp-ls-enable {
            type boolean;
            description "support bgp ls capacity.";
        }
	    leaf bgp-fs-enable {
            type boolean;
            description "support bgp fs capacity.";
        }
    }


    grouping snmp-connection {
        description "The bgp-config of a connection between controller and device.";
        leaf snmp-ip {
            type inet:ip-address;
            description "The ip of the connection.";
        }
        leaf name {
            type string;
            description "The name of the connection.";
        }
        leaf moc {
            type string;
            description "The moc of the connection.";
        }
        leaf snmp-community {
            type string;
            description "The snmp-community of the connection.";
        }
        leaf snmp-write-community {
            type string;
            description "The snmp-write-community of the connection.";
        }
        leaf snmp-version {
            type snmp-version-type;
            description "The snmp-version of the connection.";
        }
        leaf user-name {
            type string;
            description "The user-name of the connection.";
        }
        leaf context-name {
            type string;
            description "The context-name of the connection.";
        }
        leaf snmp-port {
            type uint16;
            description "The snmp-port of the connection.";
        }
        leaf timeout {
            type int32;
            description "The timeout of the connection.";
        }
        leaf retry {
            type int32;
            description "The retry times of the connection.";
        }

        leaf snmpv3-security-Level {
            type snmpv3-security-Level;
            description "The snmpv3-security-Level of the connection.";
        }
        leaf snmpv3-encry-protocol {
            type snmp-encry-protocol-type;
            description "The snmpv3-encry-protocol of the connection.";
        }
        leaf snmpv3-encry-password {
            type string;
            description "The snmpv3-encry-password of the connection.";
        }
        leaf snmpv3-auth-protocol {
            type snmp-auth-protocol-type;
            description "The snmpv3-auth-protocol of the connection.";
        }
        leaf snmpv3-auth-password {
            type string;
            description "The snmpv3-auth-password of the connection.";
        }
    }

    grouping device {
        leaf node-id {
            type inv:node-id;
            description "English:The nodeid of the device (mac).
                         ä¸­æ–‡ï¼šè®¾å¤‡èŠ‚ç‚¹æè¿°ä¿¡æ¯ã€‚";
        }
        leaf node-type{
            type node-type;
            description "The node type of the device in network.";
        }
        leaf protocol-node-id {
            type inv:node-id;
            description "The protocol nodeid of the device.";
        }
        leaf router-id {
            type inet:ip-address;
            description "The ip of the device(most ip of loopback1).";
        }
        leaf bgplu-router-id {
            type inet:ip-address;
            description "The ip for bgplu.";
        }

        container nni {
            leaf nni-ip {
                type inet:ip-address;
                description "The nni-ip of the node.";
            }
            leaf if-name {
                type string;
                description "The nni-port name of the node.";
            }
            description "The nni-cfg of the device.";
        }

        leaf vendor {
            description "The vendor of the device.";
            type enumeration {
                enum "Unknown" {
                    value 1;
                    description "Unknown.";
                }
                enum "ZTE" {
                    value 2;
                    description "ZTE.";
                }
            }
        }

        leaf device-role {
            description "The vendor of the device.";
            type device-role;
        }

        leaf device-type {
            type string;
            description "The type of the device.";
        }

        leaf device-model {
            type device-model;
            description "The type of the device.";
        }

        leaf device-description {
            type string;
            description "The description of the device.";
        }
    }

    typedef device-role {
        type enumeration {
           enum "UCPE" {
               value 1;
               description "UCPE.";
           }
           enum "VMSR" {
               value 2;
               description "VMSR.";
           }
           enum "vMSR-UME" {
               value 3;
               description "VMSR.";
           }
       }
    }

    typedef device-model{
        type enumeration {
            enum "6150" {
              value 1;
              description "ZXCTN_6150 series.";
            }
            enum "9000E" {
              value 2;
              description "ZXCTN_9000E series.";
            }
            enum "M6000" {
              value 3;
              description "ZXCTN_M6000 series.";
            }
            enum "T8K" {
              value 4;
              description "ZXCTN_T8000 series.";
            }
            enum "15K" {
              value 5;
              description "ZXCTN_15000 series.";
            }
            enum "simulate" {
               value 6;
               description "simulate series.";
            }
            enum "default" {
               value 7;
               description "default.";
            }
        }
    }
    grouping device-cfg {
        uses device;

        container pcep-connection {
            uses pcep-connection;
        }

        container bgp-connection {
            uses bgp-connection;
        }

        container restconf-connection {
            uses restconf-connection;
        }

        container netconf-connection {
            uses netconf-connection;
        }

        container snmp-connection {
            uses snmp-connection;
        }

        container cli-connection {
            uses cli-connection;
        }

    }

    container ports-config-nodes {
        config true;
        list node-ports {
            config true;
            key "node-id";
            leaf node-id {
                type inv:node-id;
                description "English:The nodeid of the device (mac).";
            }
            list ports {
                key "name";
                uses base-model:port;
            }
        }
    }

    grouping rpc-result{
        list fail-node{
              key "node-id";
            leaf node-id {
                type inv:node-id;
            }
            leaf error-msg{
                type string;
            }
        }
    }

    identity device-context {
        description "A device-context is a classifier for device elements .";
    }

    grouping device-group {
        list device-group {
            config true;
            key "node-id";
            ext:context-instance "device-context";
            uses device-cfg;
        }
    }

    grouping controllers {
        list controller {
            key "node-id";
            leaf node-id {
                type inv:node-id;
                mandatory true;
            }
            container controller-detail {
                uses device-cfg;
            }
            container controller-devices{
                uses device-group;
            }
        }
    }

    grouping plugins {
        container dna {
            uses device-cfg;
        }
    }

    container devices {
        config true;

        container plugin {
            uses plugins;
        }

        container controllers {
            uses controllers;
        }

        list device {
            config true;
            key "node-id";
            ext:context-instance "device-context";
            uses device-cfg;
        }
    }

    rpc add-devices {
        input {
            list adding-device {
                key "node-id";
                uses device-cfg;
            }
        }

        output {
           uses rpc-result;
        }
    }

    rpc get-if-address {
        input {
            leaf node-id {
                type inv:node-id;
            }
            leaf if-name {
                type string;
            }
        }

        output {
             leaf if-ip {
                 type inet:ip-address;
                 config false;
                 description "The ip of the interface get from inv.";
             }
        }
    }

    rpc update-devices {
        input {
            list updating-device {
                key "node-id";
                uses device-cfg;
            }
        }

        output {
           uses rpc-result;
        }
    }

    rpc delete-devices {
        input {
            list deleting-device {
                leaf node-id {
                    type inv:node-id;
                }
            }
        }

        output {
           uses rpc-result;
        }
    }

    grouping connect-detail{
        leaf node-id {
            type inv:node-id;
            description "The nodeid of the device.";
        }

        leaf node-type {
            type node-type;
            description "Type of the device.";
        }

        leaf netconf-ip {
            type inet:ip-address;
            description "The ip of a connection between controller and device.";
        }

        leaf restconf-ip {
            type inet:ip-address;
            description "The ip of the connection.";
        }
    }

    typedef authentication-status {
        type enumeration {
            enum "OK" {
                value 1;
            }
            enum "FAIL" {
                value 2;
            }
            enum "UNKOWN" {
                value 3;
            }
        }
    }

    grouping authentication-device {
        leaf serial-id {
            type string;
        }
        leaf ne-type {
            type string;
        }
        leaf ip-address {
            type string;
        }
        leaf mac {
            type string;
        }
    }

    grouping authentication-devices {
        list devices{
            key "serial-id";
            uses authentication-device;
        }
    }

    notification  authentication-devices-notification {
        leaf event-id{
            type string;
        }
        uses authentication-devices;
    }

    rpc set-device-authentication-result {
        input {
            list nodes{
                key "node-id";
                leaf node-id {
                    type inv:node-id;
                }
                leaf serial-id {
                    type string;
                }
                leaf authorized {
                    type boolean;
                }
            }
        }
        output{
            list nodes{
                key "node-id";
                leaf node-id {
                    type inv:node-id;
                }
                leaf serial-id {
                    type string;
                }
                leaf error-code {
                    type uint32;
                }
            }
        }
    }

    rpc get-authentication-devices {
        input {
            leaf status {
                type authentication-status;
            }

            list serial-ids{
                leaf serial-id {
                    type string;
                }
            }
        }
        output{
            uses authentication-device;
        }
    }

    rpc get-connect {
        input {
            leaf node-id {
                type inv:node-id;
                description "The nodeid of the device (mac).";
            }
        }
        output {
            list connects {
                key "node-id";
                uses connect-detail;
            }
        }
    }

    rpc get-router-id {
        input {
            leaf node-id {
                type inv:node-id;
                description "The nodeid of the device (mac).";
            }
        }
        output {
            leaf router-id {
                type inet:ip-address;
                description "The ip of the device(most ip of loopback1).";
            }
        }
    }

    rpc get-device-model-by-node-id {
        input {
            leaf node-id {
                type inv:node-id;
                description "The nodeid of the device (mac).";
            }
        }
        output {
            leaf device-model {
                type device-model;
                description "The type of the device.";
            }
        }
    }


    rpc get-device-model-by-device-type {
        input {
            leaf device-type {
                type string;
                description "The type of the device.";
            }
        }
        output {
            leaf device-model {
                type device-model;
                description "The type of the device.";
            }
        }
    }

    grouping node-nni {
        choice node-nni {
            case ip {
                leaf nni-ip {
                    type inet:ip-address;
                    description "The nni-ip of the node.";
                }

            }

            case interface {
                leaf if-name {
                    type string;
                    description "The nni-port name of the node.";
                }

                leaf if-ip {
                    type inet:ip-address;
                    config false;
                    description "The ip of the interface get from inv.";
                }
            }
        }
    }

    rpc add-node-nni {
        input {
            leaf node-id {
                type inv:node-id;
                description "The nodeid of the device.";
            }

            uses node-nni;
        }
    }

    rpc delete-node-nni {
        input {
            leaf node-id {
                type inv:node-id;
                description "The nodeid of the device.";
            }
        }
    }

    rpc get-node-nni {
        input {
            leaf node-id {
                type inv:node-id;
                description "The nodeid of the device.";
            }
        }

        output {
            uses node-nni;
        }
    }

    rpc is-h-controller {
        output {
            leaf result {
               type boolean;
               description "true : h controller, false : d controller." ;
            }
        }
    }

   rpc get-devices {
       input {
           leaf node-type {
               type node-type;
           }
           uses node-list;
       }
       output {
           list device-info {
               container parent {
                  uses device-cfg;
               }
               uses device-cfg;
               description "H controller get all D controller device info." ;
           }
       }
   }

    rpc get-controllers {
        input {
            uses node-list;
        }
        output {
            uses controllers;
        }
    }


    rpc  get-all-device {
        output {
            list device-info {
                uses device-cfg;
                description "H controller get all D controller device info." ;
            }
        }
    }

    rpc  get-if-name {
        input {
            leaf node-id {
                type inv:node-id;
                description "The nodeid of the device.";
            }

            leaf ip {
                type inet:ip-address;
                description "The nni-ip of the node.";
            }
        }
        output {
            leaf if-name {
                type string;
                description "The nni-port name of the node.";
            }
        }
    }


   grouping vpn-ip {
        leaf ipv4-address {
            type inet:ipv4-address;
            description "The ipv4 address of the interface.";
        }

        leaf ipv4-mask {
            type inet:ipv4-address;
            description "The ipv4 mask of the interface.";
        }

        leaf vrf-name {
            type string;
            description "The nni-port name of the node.";
        }
   }

    grouping port-config-result {
        leaf node-id {
            type inv:node-id;
        }

        choice result {
            case success {
                uses base-model:ports;
            }
            case fail {
                leaf reason {
                    type string {
                        length "0 .. 5000";
                    }
                    description "The failed reason info.";
                }
            }
        }
    }

    rpc port-config{
        input {
            leaf txid {
                type string{
                    length "1..255";
                }
                description "txid for the port";
            }
            leaf operate {
                type base-model:operation-type;
                default create;
                description "add or delete";
            }
             uses base-model:node-ports;
        }
        output {
            uses port-config-result;
        }
    }

    rpc get-node-bgp-lu-route-id {
        input {
            uses node-id-bgp-lu-list-input;
        }
        output {
            uses node-id-bgp-lu-list-output;
        }
    }
    grouping node-id-bgp-lu-list-output {
        list node-id-bgp-lu-list {
            key node-id-bgp-lu;
            leaf node-id-bgp-lu {
                type inv:node-id;
            }
            leaf bgp-lu-route-id {
                type inet:ipv4-address;
            }
        }
    }
    grouping node-id-bgp-lu-list-input {
        list node-id-list {
            key node-id;
            leaf node-id {
                type inv:node-id;
            }
        }
    }

    notification  device-netconf-change {
         list device-netconf{
              leaf change-type {
                   type base-model:operation-type;
              }
              uses device-netconf-detail;
         }
    }

    notification device-change {
        leaf  change-type{
            type base-model:operation-type;
        }

        leaf controller{
            type inet:ip-address;
        }

        uses device-group;
    }
}
