module base-model {
    yang-version 1;
    namespace "urn:zte:ngip:ipsdn:base-model";
    prefix "base-model";
    import ietf-inet-types {prefix inet; revision-date "2010-09-24"; }
    import opendaylight-inventory {prefix inv;revision-date "2013-08-19";}

    organization "zte";

    description
      "YANG version of the base-model.";

    revision "2017-03-29" {
        description "Initial revision of base model";
    }

   grouping vpn-ip {
        leaf ipv4-address {
            type inet:ipv4-address;
            description "The ipv4 address of the interface.";
        }

        leaf ipv4-mask {
            type inet:ipv4-address;
            description "The ipv4 mask of the interface.";
        }

        leaf vrf-name {
            type string;
            description "The vrf name of the node.";
        }
   }

    typedef vlan-bitmap{
        type int32 {
            range "1..4094";
        }
    }

    typedef operation-type {
         type enumeration {
             enum create {
                 value 1;
             }
             enum remove {
                 value 2;
             }
             enum update {
                 value 3;
             }
         }
     }

    typedef port-type {
        description "type of port.";
        type enumeration {
            enum "vlan" {
                value 1;
                description "vlan";
            }
            enum "loopback" {
                value 2;
                description "loopback";
            }
        }
    }

    grouping access-type {
        choice access-type {
            description "access-type";
            case port{
                description "port. CRD";
            }
            case dot1q {
                description "Dot1Q";
                leaf dot1q-vlan-bitmap {
                    type vlan-bitmap;
                    description "Dot1Q Vlan Bitmap. CRD" ;
                }
            }
            case qinq {
                description "QinQ. CRD";
                leaf qinq-internal-vlan-bitmap {
                    type vlan-bitmap;
                    description "QinQ internal vlan bitmap." ;
                }
                leaf qinq-external-vlan-bitmap {
                    type vlan-bitmap;
                    description "QinQ external vlan bitmap." ;
                }
            }
            case vlanrange {
                description "vlanr range. CRUD";
                list vlan-range {
                    key "vlan-begin";
                    leaf vlan-begin {
                        type vlan-bitmap;
                        description "Vlan Bitmap." ;
                    }
                    leaf vlan-end {
                        type vlan-bitmap;
                        description "Vlan Bitmap." ;
                    }
                }
            }
        }
    }

    grouping switch-vlan {
        leaf only-config-l2 {
            type boolean;
            default true;
        }
        uses vlan-attribute;
    }

    grouping vlan-attribute {
        container vlan-attribute {
            list pvid-port {
                key "port-name";
                uses switch-port;
            }
            list tag-port {
                key "port-name";
                uses switch-port;
            }
            list untag-port {
                key "port-name";
                uses switch-port;
            }
        }
    }

    grouping switch-port {
        leaf port-name {
            type string;
        }
        leaf mode {
            type switch-port-mode;
        }
    }

    typedef switch-port-mode {
        type enumeration {
            enum access {
                value 1;
                description "access mode";
            }
            enum trunk {
                value 2;
                description "trunk mode";
            }
            enum hybrid {
                value 3;
                description "hybrid mode";
            }
        }
    }

    grouping node-ports{
        leaf node-id {
            type inv:node-id;
            description "English:The nodeid of the device (mac).";
        }

         uses ports;
    }

    grouping ports {
        list ports {
            uses port;
        }
    }

    grouping port {
        leaf name {
            type string;
            description "The port name of the node, eg: fei-0/1/0/1.1, tunnel1, loopback1";
             mandatory true;
        }

        leaf if-name {
            type string;
            description "parent port name, eg: fei-0/1/0/1";
        }
        leaf port-type {
            type port-type;
            description "vlan or loopback";
        }

        uses vpn-ip;
        uses access-type;
        uses switch-vlan;
    }
}
